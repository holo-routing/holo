module ietf-rip-holo-deviations {
  yang-version 1.1;
  namespace "http://holo-routing.org/yang/ietf-rip-holo-deviations";
  prefix ietf-rip-holo-deviations;

  import ietf-routing {
    prefix rt;
  }

  import ietf-rip {
    prefix rip;
  }

  organization
    "Holo Routing Stack";

  description
    "This module defines deviation statements for the ietf-rip
     module.";

  deviation "/rt:routing/rt:control-plane-protocols/rt:control-plane-protocol/rip:rip/rip:originate-default-route" {
    deviate not-supported;
  }

  /*
  deviation "/rt:routing/rt:control-plane-protocols/rt:control-plane-protocol/rip:rip/rip:originate-default-route/rip:enabled" {
    deviate not-supported;
  }
  */

  /*
  deviation "/rt:routing/rt:control-plane-protocols/rt:control-plane-protocol/rip:rip/rip:originate-default-route/rip:route-policy" {
    deviate not-supported;
  }
  */


  deviation "/rt:routing/rt:control-plane-protocols/rt:control-plane-protocol/rip:rip/rip:distribute-list" {
    deviate not-supported;
  }

  /*
  deviation "/rt:routing/rt:control-plane-protocols/rt:control-plane-protocol/rip:rip/rip:distribute-list/rip:prefix-set-name" {
    deviate not-supported;
  }
  */

  /*
  deviation "/rt:routing/rt:control-plane-protocols/rt:control-plane-protocol/rip:rip/rip:distribute-list/rip:direction" {
    deviate not-supported;
  }
  */

  /*
  deviation "/rt:routing/rt:control-plane-protocols/rt:control-plane-protocol/rip:rip/rip:distribute-list/rip:if-name" {
    deviate not-supported;
  }
  */

  deviation "/rt:routing/rt:control-plane-protocols/rt:control-plane-protocol/rip:rip/rip:redistribute" {
    deviate not-supported;
  }

  /*
  deviation "/rt:routing/rt:control-plane-protocols/rt:control-plane-protocol/rip:rip/rip:redistribute/rip:bgp" {
    deviate not-supported;
  }
  */

  /*
  deviation "/rt:routing/rt:control-plane-protocols/rt:control-plane-protocol/rip:rip/rip:redistribute/rip:bgp/rip:asn" {
    deviate not-supported;
  }
  */

  /*
  deviation "/rt:routing/rt:control-plane-protocols/rt:control-plane-protocol/rip:rip/rip:redistribute/rip:bgp/rip:metric" {
    deviate not-supported;
  }
  */

  /*
  deviation "/rt:routing/rt:control-plane-protocols/rt:control-plane-protocol/rip:rip/rip:redistribute/rip:bgp/rip:route-policy" {
    deviate not-supported;
  }
  */

  /*
  deviation "/rt:routing/rt:control-plane-protocols/rt:control-plane-protocol/rip:rip/rip:redistribute/rip:cg-nat" {
    deviate not-supported;
  }
  */

  /*
  deviation "/rt:routing/rt:control-plane-protocols/rt:control-plane-protocol/rip:rip/rip:redistribute/rip:cg-nat/rip:metric" {
    deviate not-supported;
  }
  */

  /*
  deviation "/rt:routing/rt:control-plane-protocols/rt:control-plane-protocol/rip:rip/rip:redistribute/rip:cg-nat/rip:route-policy" {
    deviate not-supported;
  }
  */

  /*
  deviation "/rt:routing/rt:control-plane-protocols/rt:control-plane-protocol/rip:rip/rip:redistribute/rip:connected" {
    deviate not-supported;
  }
  */

  /*
  deviation "/rt:routing/rt:control-plane-protocols/rt:control-plane-protocol/rip:rip/rip:redistribute/rip:connected/rip:metric" {
    deviate not-supported;
  }
  */

  /*
  deviation "/rt:routing/rt:control-plane-protocols/rt:control-plane-protocol/rip:rip/rip:redistribute/rip:connected/rip:route-policy" {
    deviate not-supported;
  }
  */

  /*
  deviation "/rt:routing/rt:control-plane-protocols/rt:control-plane-protocol/rip:rip/rip:redistribute/rip:ipsec" {
    deviate not-supported;
  }
  */

  /*
  deviation "/rt:routing/rt:control-plane-protocols/rt:control-plane-protocol/rip:rip/rip:redistribute/rip:ipsec/rip:metric" {
    deviate not-supported;
  }
  */

  /*
  deviation "/rt:routing/rt:control-plane-protocols/rt:control-plane-protocol/rip:rip/rip:redistribute/rip:ipsec/rip:route-policy" {
    deviate not-supported;
  }
  */

  /*
  deviation "/rt:routing/rt:control-plane-protocols/rt:control-plane-protocol/rip:rip/rip:redistribute/rip:isis" {
    deviate not-supported;
  }
  */

  /*
  deviation "/rt:routing/rt:control-plane-protocols/rt:control-plane-protocol/rip:rip/rip:redistribute/rip:isis/rip:instance" {
    deviate not-supported;
  }
  */

  /*
  deviation "/rt:routing/rt:control-plane-protocols/rt:control-plane-protocol/rip:rip/rip:redistribute/rip:isis/rip:level" {
    deviate not-supported;
  }
  */

  /*
  deviation "/rt:routing/rt:control-plane-protocols/rt:control-plane-protocol/rip:rip/rip:redistribute/rip:isis/rip:metric" {
    deviate not-supported;
  }
  */

  /*
  deviation "/rt:routing/rt:control-plane-protocols/rt:control-plane-protocol/rip:rip/rip:redistribute/rip:isis/rip:route-policy" {
    deviate not-supported;
  }
  */

  /*
  deviation "/rt:routing/rt:control-plane-protocols/rt:control-plane-protocol/rip:rip/rip:redistribute/rip:nat" {
    deviate not-supported;
  }
  */

  /*
  deviation "/rt:routing/rt:control-plane-protocols/rt:control-plane-protocol/rip:rip/rip:redistribute/rip:nat/rip:metric" {
    deviate not-supported;
  }
  */

  /*
  deviation "/rt:routing/rt:control-plane-protocols/rt:control-plane-protocol/rip:rip/rip:redistribute/rip:nat/rip:route-policy" {
    deviate not-supported;
  }
  */

  /*
  deviation "/rt:routing/rt:control-plane-protocols/rt:control-plane-protocol/rip:rip/rip:redistribute/rip:ospfv2" {
    deviate not-supported;
  }
  */

  /*
  deviation "/rt:routing/rt:control-plane-protocols/rt:control-plane-protocol/rip:rip/rip:redistribute/rip:ospfv2/rip:instance" {
    deviate not-supported;
  }
  */

  /*
  deviation "/rt:routing/rt:control-plane-protocols/rt:control-plane-protocol/rip:rip/rip:redistribute/rip:ospfv2/rip:route-type" {
    deviate not-supported;
  }
  */

  /*
  deviation "/rt:routing/rt:control-plane-protocols/rt:control-plane-protocol/rip:rip/rip:redistribute/rip:ospfv2/rip:metric" {
    deviate not-supported;
  }
  */

  /*
  deviation "/rt:routing/rt:control-plane-protocols/rt:control-plane-protocol/rip:rip/rip:redistribute/rip:ospfv2/rip:route-policy" {
    deviate not-supported;
  }
  */

  /*
  deviation "/rt:routing/rt:control-plane-protocols/rt:control-plane-protocol/rip:rip/rip:redistribute/rip:ospfv3" {
    deviate not-supported;
  }
  */

  /*
  deviation "/rt:routing/rt:control-plane-protocols/rt:control-plane-protocol/rip:rip/rip:redistribute/rip:ospfv3/rip:instance" {
    deviate not-supported;
  }
  */

  /*
  deviation "/rt:routing/rt:control-plane-protocols/rt:control-plane-protocol/rip:rip/rip:redistribute/rip:ospfv3/rip:route-type" {
    deviate not-supported;
  }
  */

  /*
  deviation "/rt:routing/rt:control-plane-protocols/rt:control-plane-protocol/rip:rip/rip:redistribute/rip:ospfv3/rip:metric" {
    deviate not-supported;
  }
  */

  /*
  deviation "/rt:routing/rt:control-plane-protocols/rt:control-plane-protocol/rip:rip/rip:redistribute/rip:ospfv3/rip:route-policy" {
    deviate not-supported;
  }
  */

  /*
  deviation "/rt:routing/rt:control-plane-protocols/rt:control-plane-protocol/rip:rip/rip:redistribute/rip:ripv2" {
    deviate not-supported;
  }
  */

  /*
  deviation "/rt:routing/rt:control-plane-protocols/rt:control-plane-protocol/rip:rip/rip:redistribute/rip:ripv2/rip:instance" {
    deviate not-supported;
  }
  */

  /*
  deviation "/rt:routing/rt:control-plane-protocols/rt:control-plane-protocol/rip:rip/rip:redistribute/rip:ripv2/rip:metric" {
    deviate not-supported;
  }
  */

  /*
  deviation "/rt:routing/rt:control-plane-protocols/rt:control-plane-protocol/rip:rip/rip:redistribute/rip:ripv2/rip:route-policy" {
    deviate not-supported;
  }
  */

  /*
  deviation "/rt:routing/rt:control-plane-protocols/rt:control-plane-protocol/rip:rip/rip:redistribute/rip:ripng" {
    deviate not-supported;
  }
  */

  /*
  deviation "/rt:routing/rt:control-plane-protocols/rt:control-plane-protocol/rip:rip/rip:redistribute/rip:ripng/rip:instance" {
    deviate not-supported;
  }
  */

  /*
  deviation "/rt:routing/rt:control-plane-protocols/rt:control-plane-protocol/rip:rip/rip:redistribute/rip:ripng/rip:metric" {
    deviate not-supported;
  }
  */

  /*
  deviation "/rt:routing/rt:control-plane-protocols/rt:control-plane-protocol/rip:rip/rip:redistribute/rip:ripng/rip:route-policy" {
    deviate not-supported;
  }
  */

  /*
  deviation "/rt:routing/rt:control-plane-protocols/rt:control-plane-protocol/rip:rip/rip:redistribute/rip:static" {
    deviate not-supported;
  }
  */

  /*
  deviation "/rt:routing/rt:control-plane-protocols/rt:control-plane-protocol/rip:rip/rip:redistribute/rip:static/rip:metric" {
    deviate not-supported;
  }
  */

  /*
  deviation "/rt:routing/rt:control-plane-protocols/rt:control-plane-protocol/rip:rip/rip:redistribute/rip:static/rip:route-policy" {
    deviate not-supported;
  }
  */

  deviation "/rt:routing/rt:control-plane-protocols/rt:control-plane-protocol/rip:rip/rip:maximum-paths" {
    deviate not-supported;
  }

  deviation "/rt:routing/rt:control-plane-protocols/rt:control-plane-protocol/rip:rip/rip:output-delay" {
    deviate not-supported;
  }

  deviation "/rt:routing/rt:control-plane-protocols/rt:control-plane-protocol/rip:rip/rip:timers/rip:holddown-interval" {
    deviate not-supported;
  }

  deviation "/rt:routing/rt:control-plane-protocols/rt:control-plane-protocol/rip:rip/rip:interfaces/rip:interface/rip:authentication/rip:auth-type-selection/rip:auth-key-chain" {
    deviate not-supported;
  }

  /*
  deviation "/rt:routing/rt:control-plane-protocols/rt:control-plane-protocol/rip:rip/rip:interfaces/rip:interface/rip:authentication/rip:auth-type-selection/rip:auth-key-chain/rip:key-chain" {
    deviate not-supported;
  }
  */

  deviation "/rt:routing/rt:control-plane-protocols/rt:control-plane-protocol/rip:rip/rip:interfaces/rip:interface/rip:originate-default-route" {
    deviate not-supported;
  }

  /*
  deviation "/rt:routing/rt:control-plane-protocols/rt:control-plane-protocol/rip:rip/rip:interfaces/rip:interface/rip:originate-default-route/rip:enabled" {
    deviate not-supported;
  }
  */

  /*
  deviation "/rt:routing/rt:control-plane-protocols/rt:control-plane-protocol/rip:rip/rip:interfaces/rip:interface/rip:originate-default-route/rip:route-policy" {
    deviate not-supported;
  }
  */


  deviation "/rt:routing/rt:control-plane-protocols/rt:control-plane-protocol/rip:rip/rip:interfaces/rip:interface/rip:summary-address" {
    deviate not-supported;
  }

  /*
  deviation "/rt:routing/rt:control-plane-protocols/rt:control-plane-protocol/rip:rip/rip:interfaces/rip:interface/rip:summary-address/rip:address" {
    deviate not-supported;
  }
  */

  /*
  deviation "/rt:routing/rt:control-plane-protocols/rt:control-plane-protocol/rip:rip/rip:interfaces/rip:interface/rip:summary-address/rip:metric" {
    deviate not-supported;
  }
  */

  deviation "/rt:routing/rt:control-plane-protocols/rt:control-plane-protocol/rip:rip/rip:interfaces/rip:interface/rip:timers" {
    deviate delete {
      must 'invalid-interval >= (update-interval * 3)';
    }
  }

  deviation "/rt:routing/rt:control-plane-protocols/rt:control-plane-protocol/rip:rip/rip:interfaces/rip:interface/rip:timers/rip:update-interval" {
    deviate not-supported;
  }

  deviation "/rt:routing/rt:control-plane-protocols/rt:control-plane-protocol/rip:rip/rip:interfaces/rip:interface/rip:timers/rip:holddown-interval" {
    deviate not-supported;
  }

  deviation "/rt:routing/rt:control-plane-protocols/rt:control-plane-protocol/rip:rip/rip:ipv4/rip:routes/rip:route/rip:holddown" {
    deviate not-supported;
  }

  deviation "/rt:routing/rt:control-plane-protocols/rt:control-plane-protocol/rip:rip/rip:ipv4/rip:routes/rip:route/rip:flush-expire-before-holddown" {
    deviate not-supported;
  }

  deviation "/rt:routing/rt:control-plane-protocols/rt:control-plane-protocol/rip:rip/rip:ipv6/rip:routes/rip:route/rip:holddown" {
    deviate not-supported;
  }

  deviation "/rt:routing/rt:control-plane-protocols/rt:control-plane-protocol/rip:rip/rip:ipv6/rip:routes/rip:route/rip:flush-expire-before-holddown" {
    deviate not-supported;
  }
}
