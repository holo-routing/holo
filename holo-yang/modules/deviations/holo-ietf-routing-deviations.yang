module holo-ietf-routing-deviations {
  yang-version 1.1;
  namespace "http://holo-routing.org/yang/holo-ietf-routing-deviations";
  prefix holo-ietf-routing-deviations;

  import ietf-routing {
    prefix rt;
  }

  organization
    "Holo Routing Stack";

  description
    "This module defines deviation statements for the ietf-routing
     module.";

  /*
   * Added constraints
   */

  deviation "/rt:routing/rt:control-plane-protocols/rt:control-plane-protocol" {
    deviate add {
      must 'not(derived-from-or-self(rt:type, "rt:static")) or rt:name = "main"' {
        error-message
          "The static protocol instance must be named \"main\".";
      }
    }
  }

  deviation "/rt:routing/rt:control-plane-protocols/rt:control-plane-protocol/rt:type" {
    deviate add {
      must 'not(derived-from-or-self(., "rt:direct"))' {
        error-message
          "The direct protocol isn't configurable.";
      }
      must 'derived-from(., "rt:routing-protocol")'
         + ' or not(derived-from-or-self(., "rt:routing-protocol"))' {
        error-message
          "Invalid protocol type.";
      }
    }
  }

  /*
   * Not supported nodes
   */

  deviation "/rt:routing/rt:router-id" {
    deviate not-supported;
  }

  deviation "/rt:routing/rt:interfaces" {
    deviate not-supported;
  }

  deviation "/rt:routing-state" {
    deviate not-supported;
  }

  deviation "/rt:routing/rt:ribs/rt:rib/rt:active-route" {
    deviate not-supported;
  }
}
