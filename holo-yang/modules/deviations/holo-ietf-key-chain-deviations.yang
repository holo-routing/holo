module holo-ietf-key-chain-deviations {
  yang-version 1.1;
  namespace "http://holo-routing.org/yang/holo-ietf-key-chain-deviations";
  prefix holo-ietf-key-chain-deviations;

  import ietf-key-chain {
    prefix key-chain;
  }

  organization
    "Holo Routing Stack";

  description
    "This module defines deviation statements for the ietf-key-chain
     module.";

  /*
  deviation "/key-chain:key-chains" {
    deviate not-supported;
  }
  */

  /*
  deviation "/key-chain:key-chains/key-chain:key-chain" {
    deviate not-supported;
  }
  */

  /*
  deviation "/key-chain:key-chains/key-chain:key-chain/key-chain:name" {
    deviate not-supported;
  }
  */

  /*
  deviation "/key-chain:key-chains/key-chain:key-chain/key-chain:description" {
    deviate not-supported;
  }
  */

  /*
  deviation "/key-chain:key-chains/key-chain:key-chain/key-chain:last-modified-timestamp" {
    deviate not-supported;
  }
  */

  /*
  deviation "/key-chain:key-chains/key-chain:key-chain/key-chain:key" {
    deviate not-supported;
  }
  */

  /*
  deviation "/key-chain:key-chains/key-chain:key-chain/key-chain:key/key-chain:key-id" {
    deviate not-supported;
  }
  */

  /*
  deviation "/key-chain:key-chains/key-chain:key-chain/key-chain:key/key-chain:lifetime" {
    deviate not-supported;
  }
  */

  /*
  deviation "/key-chain:key-chains/key-chain:key-chain/key-chain:key/key-chain:lifetime/key-chain:lifetime" {
    deviate not-supported;
  }
  */

  /*
  deviation "/key-chain:key-chains/key-chain:key-chain/key-chain:key/key-chain:lifetime/key-chain:lifetime/key-chain:send-and-accept-lifetime" {
    deviate not-supported;
  }
  */

  /*
  deviation "/key-chain:key-chains/key-chain:key-chain/key-chain:key/key-chain:lifetime/key-chain:lifetime/key-chain:send-and-accept-lifetime/key-chain:send-accept-lifetime" {
    deviate not-supported;
  }
  */

  /*
  deviation "/key-chain:key-chains/key-chain:key-chain/key-chain:key/key-chain:lifetime/key-chain:lifetime/key-chain:send-and-accept-lifetime/key-chain:send-accept-lifetime/key-chain:lifetime" {
    deviate not-supported;
  }
  */

  /*
  deviation "/key-chain:key-chains/key-chain:key-chain/key-chain:key/key-chain:lifetime/key-chain:lifetime/key-chain:send-and-accept-lifetime/key-chain:send-accept-lifetime/key-chain:lifetime/key-chain:always" {
    deviate not-supported;
  }
  */

  /*
  deviation "/key-chain:key-chains/key-chain:key-chain/key-chain:key/key-chain:lifetime/key-chain:lifetime/key-chain:send-and-accept-lifetime/key-chain:send-accept-lifetime/key-chain:lifetime/key-chain:always/key-chain:always" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:start-date-time" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time/key-chain:infinite" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time/key-chain:infinite/key-chain:no-end-time" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time/key-chain:duration" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time/key-chain:duration/key-chain:duration" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time/key-chain:end-date-time" {
    deviate not-supported;
  }
  */

  /*
  deviation "/key-chain:key-chains/key-chain:key-chain/key-chain:key/key-chain:lifetime/key-chain:lifetime/key-chain:send-and-accept-lifetime/key-chain:send-accept-lifetime/key-chain:lifetime/key-chain:start-end-time/key-chain:end-time/key-chain:end-date-time/key-chain:end-date-time" {
    deviate not-supported;
  }
  */

  /*
  deviation "/key-chain:key-chains/key-chain:key-chain/key-chain:key/key-chain:crypto-algorithm" {
    deviate not-supported;
  }
  */

  /*
  deviation "/key-chain:key-chains/key-chain:key-chain/key-chain:key/key-chain:key-string" {
    deviate not-supported;
  }
  */

  /*
  deviation "/key-chain:key-chains/key-chain:key-chain/key-chain:key/key-chain:key-string/key-chain:key-string-style" {
    deviate not-supported;
  }
  */

  /*
  deviation "/key-chain:key-chains/key-chain:key-chain/key-chain:key/key-chain:key-string/key-chain:key-string-style/key-chain:keystring" {
    deviate not-supported;
  }
  */

  /*
  deviation "/key-chain:key-chains/key-chain:key-chain/key-chain:key/key-chain:key-string/key-chain:key-string-style/key-chain:keystring/key-chain:keystring" {
    deviate not-supported;
  }
  */

  /*
  deviation "/key-chain:key-chains/key-chain:key-chain/key-chain:key/key-chain:send-lifetime-active" {
    deviate not-supported;
  }
  */

  /*
  deviation "/key-chain:key-chains/key-chain:key-chain/key-chain:key/key-chain:accept-lifetime-active" {
    deviate not-supported;
  }
  */
}
