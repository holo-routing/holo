module ietf-mpls-ldp-holo-deviations {
  yang-version 1.1;
  namespace "http://holo-routing.org/yang/ietf-mpls-ldp-holo-deviations";
  prefix ietf-mpls-ldp-holo-deviations;

  import ietf-routing {
    prefix rt;
  }

  import ietf-mpls-ldp {
    prefix ldp;
  }

  organization
    "Holo Routing Stack";

  description
    "This module defines deviation statements for the ietf-mpls-ldp
     module.";

  deviation "/rt:routing/rt:control-plane-protocols/rt:control-plane-protocol/ldp:mpls-ldp/ldp:discovery/ldp:interfaces/ldp:interface/ldp:address-families/ldp:ipv4/ldp:hello-adjacencies/ldp:hello-adjacency/ldp:flag" {
    deviate not-supported;
  }

  deviation "/rt:routing/rt:control-plane-protocols/rt:control-plane-protocol/ldp:mpls-ldp/ldp:discovery/ldp:targeted/ldp:address-families/ldp:ipv4/ldp:hello-adjacencies/ldp:hello-adjacency/ldp:flag" {
    deviate not-supported;
  }

  deviation "/rt:routing/rt:control-plane-protocols/rt:control-plane-protocol/ldp:mpls-ldp/ldp:peers/ldp:peer/ldp:address-families/ldp:ipv4/ldp:hello-adjacencies/ldp:hello-adjacency/ldp:flag" {
    deviate not-supported;
  }

  deviation "/rt:routing/rt:control-plane-protocols/rt:control-plane-protocol/ldp:mpls-ldp/ldp:global/ldp:graceful-restart" {
    deviate not-supported;
  }

  /*
  deviation "/rt:routing/rt:control-plane-protocols/rt:control-plane-protocol/ldp:mpls-ldp/ldp:global/ldp:graceful-restart/ldp:enabled" {
    deviate not-supported;
  }
  */

  /*
  deviation "/rt:routing/rt:control-plane-protocols/rt:control-plane-protocol/ldp:mpls-ldp/ldp:global/ldp:graceful-restart/ldp:reconnect-time" {
    deviate not-supported;
  }
  */

  /*
  deviation "/rt:routing/rt:control-plane-protocols/rt:control-plane-protocol/ldp:mpls-ldp/ldp:global/ldp:graceful-restart/ldp:recovery-time" {
    deviate not-supported;
  }
  */

  /*
  deviation "/rt:routing/rt:control-plane-protocols/rt:control-plane-protocol/ldp:mpls-ldp/ldp:global/ldp:graceful-restart/ldp:forwarding-holdtime" {
    deviate not-supported;
  }
  */

  deviation "/rt:routing/rt:control-plane-protocols/rt:control-plane-protocol/ldp:mpls-ldp/ldp:discovery/ldp:targeted/ldp:address-families/ldp:ipv4/ldp:target/ldp:local-address" {
    deviate not-supported;
  }

  deviation "/rt:routing/rt:control-plane-protocols/rt:control-plane-protocol/ldp:mpls-ldp/ldp:peers/ldp:peer/ldp:address-families/ldp:ipv4/ldp:hello-adjacencies/ldp:hello-adjacency/ldp:interface" {
    deviate not-supported;
  }

  deviation "/rt:routing/rt:control-plane-protocols/rt:control-plane-protocol/ldp:mpls-ldp/ldp:peers/ldp:peer/ldp:received-peer-state/ldp:graceful-restart" {
    deviate not-supported;
  }

  /*
  deviation "/rt:routing/rt:control-plane-protocols/rt:control-plane-protocol/ldp:mpls-ldp/ldp:peers/ldp:peer/ldp:received-peer-state/ldp:graceful-restart/ldp:enabled" {
    deviate not-supported;
  }
  */

  /*
  deviation "/rt:routing/rt:control-plane-protocols/rt:control-plane-protocol/ldp:mpls-ldp/ldp:peers/ldp:peer/ldp:received-peer-state/ldp:graceful-restart/ldp:reconnect-time" {
    deviate not-supported;
  }
  */

  /*
  deviation "/rt:routing/rt:control-plane-protocols/rt:control-plane-protocol/ldp:mpls-ldp/ldp:peers/ldp:peer/ldp:received-peer-state/ldp:graceful-restart/ldp:recovery-time" {
    deviate not-supported;
  }
  */

  deviation "/rt:routing/rt:control-plane-protocols/rt:control-plane-protocol/ldp:mpls-ldp/ldp:peers/ldp:peer/ldp:received-peer-state/ldp:capability/ldp:upstream-label-assignment" {
    deviate not-supported;
  }

  /*
  deviation "/rt:routing/rt:control-plane-protocols/rt:control-plane-protocol/ldp:mpls-ldp/ldp:peers/ldp:peer/ldp:received-peer-state/ldp:capability/ldp:upstream-label-assignment/ldp:enabled" {
    deviate not-supported;
  }
  */
}
