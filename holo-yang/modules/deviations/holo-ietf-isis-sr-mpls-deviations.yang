module holo-ietf-isis-sr-mpls-deviations {
  yang-version 1.1;
  namespace "http://holo-routing.org/yang/holo-ietf-isis-sr-mpls-deviations";
  prefix holo-ietf-isis-sr-mpls-deviations;

  import ietf-routing {
    prefix rt;
  }

  import ietf-isis {
    prefix isis;
  }

  import ietf-isis-sr-mpls {
    prefix isis-sr-mpls;
  }

  organization
    "Holo Routing Stack";

  description
    "This module defines deviation statements for the ietf-isis-sr-mpls
     module.";

  /*
   * Not supported nodes
   */

  deviation "/rt:routing/rt:control-plane-protocols/rt:control-plane-protocol/isis:isis/isis:database/isis:levels/isis:lsp/isis:router-capabilities/isis:router-capability/isis-sr-mpls:srms-preference" {
    deviate not-supported;
  }

  deviation "/rt:routing/rt:control-plane-protocols/rt:control-plane-protocol/isis:isis/isis:database/isis:levels/isis:lsp/isis-sr-mpls:sid-binding-tlvs" {
    deviate not-supported;
  }

  deviation "/rt:routing/rt:control-plane-protocols/rt:control-plane-protocol/isis:isis/isis:database/isis:levels/isis:lsp/isis-sr-mpls:mt-sid-binding-tlvs" {
    deviate not-supported;
  }

  deviation "/rt:routing/rt:control-plane-protocols/rt:control-plane-protocol/isis:isis/isis:interfaces/isis:interface/isis-sr-mpls:segment-routing" {
    deviate not-supported;
  }
}
