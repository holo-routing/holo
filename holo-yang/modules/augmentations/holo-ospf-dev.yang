module holo-ospf-dev {
  yang-version 1.1;
  namespace "http://holo-routing.org/yang/holo-ospf-dev";
  prefix holo-ospf-dev;

  import ietf-routing {
    prefix rt;
  }

  import ietf-ospf {
    prefix ospf;
  }

  organization
    "Holo Routing Stack";

  description
    "This module defines augment statements for the ietf-ospf
     module.";

  /*
   * Augmentations: maxage.
   */

  augment "/rt:routing/rt:control-plane-protocols/rt:control-plane-protocol/ospf:ospf/ospf:database/ospf:as-scope-lsa-type/ospf:as-scope-lsas/ospf:as-scope-lsa/ospf:version/ospf:ospfv2/ospf:ospfv2/ospf:header" {
    leaf maxage {
      type empty;
      description "LSA has reached MaxAge.";
    }
  }

  augment "/rt:routing/rt:control-plane-protocols/rt:control-plane-protocol/ospf:ospf/ospf:database/ospf:as-scope-lsa-type/ospf:as-scope-lsas/ospf:as-scope-lsa/ospf:version/ospf:ospfv3/ospf:ospfv3/ospf:header" {
    leaf maxage {
      type empty;
      description "LSA has reached MaxAge.";
    }
  }

  augment "/rt:routing/rt:control-plane-protocols/rt:control-plane-protocol/ospf:ospf/ospf:areas/ospf:area/ospf:database/ospf:area-scope-lsa-type/ospf:area-scope-lsas/ospf:area-scope-lsa/ospf:version/ospf:ospfv2/ospf:ospfv2/ospf:header" {
    leaf maxage {
      type empty;
      description "LSA has reached MaxAge.";
    }
  }

  augment "/rt:routing/rt:control-plane-protocols/rt:control-plane-protocol/ospf:ospf/ospf:areas/ospf:area/ospf:database/ospf:area-scope-lsa-type/ospf:area-scope-lsas/ospf:area-scope-lsa/ospf:version/ospf:ospfv3/ospf:ospfv3/ospf:header" {
    leaf maxage {
      type empty;
      description "LSA has reached MaxAge.";
    }
  }

  augment "/rt:routing/rt:control-plane-protocols/rt:control-plane-protocol/ospf:ospf/ospf:areas/ospf:area/ospf:virtual-links/ospf:virtual-link/ospf:database/ospf:link-scope-lsa-type/ospf:link-scope-lsas/ospf:link-scope-lsa/ospf:version/ospf:ospfv2/ospf:ospfv2/ospf:header" {
    leaf maxage {
      type empty;
      description "LSA has reached MaxAge.";
    }
  }

  augment "/rt:routing/rt:control-plane-protocols/rt:control-plane-protocol/ospf:ospf/ospf:areas/ospf:area/ospf:virtual-links/ospf:virtual-link/ospf:database/ospf:link-scope-lsa-type/ospf:link-scope-lsas/ospf:link-scope-lsa/ospf:version/ospf:ospfv3/ospf:ospfv3/ospf:header" {
    leaf maxage {
      type empty;
      description "LSA has reached MaxAge.";
    }
  }

  augment "/rt:routing/rt:control-plane-protocols/rt:control-plane-protocol/ospf:ospf/ospf:areas/ospf:area/ospf:interfaces/ospf:interface/ospf:database/ospf:link-scope-lsa-type/ospf:link-scope-lsas/ospf:link-scope-lsa/ospf:version/ospf:ospfv2/ospf:ospfv2/ospf:header" {
    leaf maxage {
      type empty;
      description "LSA has reached MaxAge.";
    }
  }

  augment "/rt:routing/rt:control-plane-protocols/rt:control-plane-protocol/ospf:ospf/ospf:areas/ospf:area/ospf:interfaces/ospf:interface/ospf:database/ospf:link-scope-lsa-type/ospf:link-scope-lsas/ospf:link-scope-lsa/ospf:version/ospf:ospfv3/ospf:ospfv3/ospf:header" {
    leaf maxage {
      type empty;
      description "LSA has reached MaxAge.";
    }
  }
}
