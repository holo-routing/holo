module holo-ietf-ospfv3-extended-lsa-deviations {
  yang-version 1.1;
  namespace "http://holo-routing.org/yang/holo-ietf-ospfv3-extended-lsa-deviations";
  prefix holo-ietf-ospfv3-extended-lsa-deviations;

  import ietf-routing {
    prefix rt;
  }

  import ietf-ospf {
    prefix ospf;
  }

  import ietf-ospfv3-extended-lsa {
    prefix ospfv3-e-lsa;
  }

  organization
    "Holo Routing Stack";

  description
    "This module defines deviation statements for the ietf-ospfv3-extended-lsa
     module.";

  /*
   * Not supported nodes
   */

  deviation "/rt:routing/rt:control-plane-protocols/rt:control-plane-protocol/ospf:ospf/ospf:areas/ospf:area/ospf:database/ospf:area-scope-lsa-type/ospf:area-scope-lsas/ospf:area-scope-lsa/ospf:version/ospf:ospfv3/ospf:ospfv3/ospf:body/ospfv3-e-lsa:e-nssa" {
    deviate not-supported;
  }

  deviation "/rt:routing/rt:control-plane-protocols/rt:control-plane-protocol/ospf:ospf/ospf:areas/ospf:area/ospfv3-e-lsa:extended-lsa-support" {
    deviate not-supported;
  }
}
