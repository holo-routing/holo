module holo-routing {
  yang-version 1.1;
  namespace "http://holo-routing.org/yang/holo-routing";
  prefix holo-routing;

  import ietf-inet-types {
    prefix "inet";
    reference "RFC 6991: Common YANG Data Types";
  }

  import ietf-interfaces {
    prefix "if";
    reference "RFC 8343: A YANG Data Model for Interface Management";
  }

  import ietf-routing {
    prefix "rt";
  }

  import ietf-bier {
    prefix "bier";
  }

  organization
    "Holo Routing Stack";

  description
    "This module defines augment statements for the ietf-routing
    module.";

  augment "/rt:routing" {
    container birts {
      description "BIER routing tables";
      list birt {
        key "sub-domain-id";
        description "BIER Routing table";
        config false;
        leaf sub-domain-id {
          config false;
          type uint8;
          description "BIER sub-domain-id";
        }
        list bfr-id {
          key "bfr-id";
          config false;
          leaf bfr-id {
            config false;
            type uint16;
            description "BFR identifier";
          }
          list birt-entry {
            key "bsl";
            config false;
            leaf bsl {
              config false;
              // FIXME: should be bier:bsl but got some issues with yang-rs
              type uint8;
              description "Bitstring length associated with the current entry";
            }
            leaf bfr-prefix {
              config false;
              type inet:ip-address;
              description "BFR's prefix";
            }
            leaf bfr-nbr {
              config false;
              type inet:ip-address;
              description "Neighbor BFR prefix";
            }
          }
        }
      }
    }

    container next-hop-tracking {
      config false;
      description
        "Next-hop addresses whose reachability is tracked on behalf of
         routing protocols.";
      list next-hop {
        key "address";
        description
          "Tracked next-hop address.";
        leaf address {
          type inet:ip-address;
          description
            "Next-hop address.";
        }
        container resolution {
          description
            "Route the next-hop address resolves through. Absent when
             the address is unreachable.";
          leaf prefix {
            type inet:ip-prefix;
            description
              "Destination prefix of the route.";
          }
          leaf protocol {
            type identityref {
              base rt:routing-protocol;
            }
            description
              "Routing protocol from which the route originated.";
          }
          leaf metric {
            type uint32;
            description
              "Metric of the route.";
          }
          uses rt:special-next-hop;
          list next-hop {
            description
              "Next hop of the route. Recursive next hops are replaced
               by the next hops they resolved to.";
            leaf outgoing-interface {
              type if:interface-ref;
              description
                "Name of the outgoing interface.";
            }
            leaf address {
              type inet:ip-address;
              description
                "Address of the next hop.";
            }
          }
        }
      }
    }
  }
}
