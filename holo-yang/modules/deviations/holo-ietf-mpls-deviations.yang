module holo-ietf-mpls-deviations {
  yang-version 1.1;
  namespace "http://holo-routing.org/yang/holo-ietf-mpls-deviations";
  prefix holo-ietf-mpls-deviations;

  import ietf-routing {
    prefix rt;
  }

  import ietf-mpls {
    prefix mpls;
  }

  organization
    "Holo Routing Stack";

  description
    "This module defines deviation statements for the ietf-mpls
     module.";

  /*
   * Not supported nodes
   */

  deviation "/rt:routing/rt:ribs/rt:rib/rt:routes/rt:route/rt:next-hop/rt:next-hop-options/rt:simple-next-hop/mpls:mpls-label-stack/mpls:entry/mpls:ttl" {
    deviate not-supported;
  }

  deviation "/rt:routing/rt:ribs/rt:rib/rt:routes/rt:route/rt:next-hop/rt:next-hop-options/rt:simple-next-hop/mpls:mpls-label-stack/mpls:entry/mpls:traffic-class" {
    deviate not-supported;
  }

  deviation "/rt:routing/rt:ribs/rt:rib/rt:routes/rt:route/rt:next-hop/rt:next-hop-options/rt:next-hop-list/rt:next-hop-list/rt:next-hop/mpls:index" {
    deviate not-supported;
  }

  deviation "/rt:routing/rt:ribs/rt:rib/rt:routes/rt:route/rt:next-hop/rt:next-hop-options/rt:next-hop-list/rt:next-hop-list/rt:next-hop/mpls:backup-index" {
    deviate not-supported;
  }

  deviation "/rt:routing/rt:ribs/rt:rib/rt:routes/rt:route/rt:next-hop/rt:next-hop-options/rt:next-hop-list/rt:next-hop-list/rt:next-hop/mpls:loadshare" {
    deviate not-supported;
  }

  deviation "/rt:routing/rt:ribs/rt:rib/rt:routes/rt:route/rt:next-hop/rt:next-hop-options/rt:next-hop-list/rt:next-hop-list/rt:next-hop/mpls:role" {
    deviate not-supported;
  }

  deviation "/rt:routing/rt:ribs/rt:rib/rt:routes/rt:route/rt:next-hop/rt:next-hop-options/rt:next-hop-list/rt:next-hop-list/rt:next-hop/mpls:mpls-label-stack/mpls:entry/mpls:ttl" {
    deviate not-supported;
  }

  deviation "/rt:routing/rt:ribs/rt:rib/rt:routes/rt:route/rt:next-hop/rt:next-hop-options/rt:next-hop-list/rt:next-hop-list/rt:next-hop/mpls:mpls-label-stack/mpls:entry/mpls:traffic-class" {
    deviate not-supported;
  }

  deviation "/rt:routing/mpls:mpls" {
    deviate not-supported;
  }
}
