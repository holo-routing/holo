module holo-ospf-reverse-metric {
    yang-version 1.1;
    namespace "http://holo-routing.org/yang/holo-ospf-reverse-metric";
    prefix holo-ospf-reverse-metric;

    import ietf-routing {
        prefix rt;
        reference
          "RFC 8349: A YANG Data Model for Routing Management
           (NMDA Version)";
    }

    import ietf-ospf {
        prefix ospf;
        reference
          "RFC 9129: YANG Data Model for the OSPF Protocol";
    }

    organization
      "Holo Routing Stack";

    contact
      "Author: Nicolas Rybowski
       <mailto:nicolas.rybowski@uclouvain.be>";

    description
      "This module defines the configuration and operational state for managing
       OSPF reverse metric functionality (RFC 9339). It is strongly inspired
       from RFC 9194: A YANG Module for IS-IS Reverse Metric.";

    reference
      "RFC 9339: OSPF Reverse Metric";

    revision 2025-09-30 {
        description
          "Initial revision.";
    }

    grouping reverse-metric-data {
        description
          "OSPF reverse metric data.";
        leaf metric {
            type ospf:ospf-link-metric;
            description
              "The reverse metric value.";
            reference
              "RFC 9339: OSPF Reverse Metric, Section 4.";
        }
        container flags {
            description
              "The reverse metric flag values.";
            leaf higher {
                type boolean;
                default "false";
                description
                  "The 'Higher' bit (H bit) (RFC9339). If true, the neighbor
                   receiving the reverse metric should only apply it if it is
                    higher than the provisioned metric value for the link.";
                reference
                  "RFC 9339: OSPF Reverse Metric, Section 4.";
            }
            leaf offset {
                type boolean;
                default "false";
                description
                  "The 'Offset' bit (O bit) (RFC9339). If true, the provided
                   reverse metric should be added to the provisioned metric.";
                reference
                  "RFC 9339: OSPF Reverse Metric, Section 4.";
            }
        }
    }

    augment "/rt:routing/rt:control-plane-protocols/"
            + "rt:control-plane-protocol/"
            + "ospf:ospf" {
        when "derived-from-or-self(../rt:type, 'ospf:ospf')" {
            description
              "This augment is only valid when the routing protocol
               instance type is 'ospf'.";
        }

        description
          "The reverse metric configuration for an OSPF instance.";

        container reverse-metric {
            description
              "Global reverse metric configuration.";
            leaf enable-receive {
                type boolean;
                default "false";
                description
                  "Enables handling of reverse metric announcements from
                   neighbors. By default, reverse metric handling is
                   disabled and must be explicitly enabled through this
                   configuration";
                reference
                  "RFC 9339: OSPF Reverse Metric, Section 7.";
            }
        }
    }

    augment "/rt:routing/rt:control-plane-protocols/"
            + "rt:control-plane-protocol/"
            + "ospf:ospf/ospf:areas/ospf:area" {
        when "derived-from-or-self(../../../rt:type, 'ospf:ospf')" {
            description
              "This augment is only valid when the routing protocol
               instance type is 'ospf'.";
        }

        description
          "The reverse metric configuration for an OSPF area.";

        container reverse-metric {
            description
              "Area reverse metric configuration.";
            leaf enable-receive {
                type boolean;
                default "false";
                description
                  "Enables handling of reverse metric announcements from
                   neighbors. By default, reverse metric handling is
                   disabled and must be explicitly enabled through this
                   configuration";
                reference
                  "RFC 9339: OSPF Reverse Metric, Section 7.";
            }
        }
    }

    augment "/rt:routing/rt:control-plane-protocols/"
          + "rt:control-plane-protocol/"
          + "ospf:ospf/ospf:areas/ospf:area/ospf:interfaces/"
          + "ospf:interface" {
        when "derived-from-or-self(../../../../../rt:type, 'ospf:ospf')" {
            description
              "This augment is only valide when the routing protocol
               instance type is 'ospf'.";
        }

        description
          "The reverse metric configuration for an OSPF link.";
        container reverse-metric {
            description
              "Interface specific reverse metric configuration. This interface
               belongs to the default topology so mtid MUST be 0.";
            leaf enable-receive {
                type boolean;
                default "false";
                description
                  "Enables handling of reverse metric announcements from
                   neighbors. By default, reverse metric handling is
                   disabled and must be explicitly enabled through this
                   configuration";
                reference
                  "RFC 9339: OSPF Reverse Metric, Section 7.";
            }
            uses reverse-metric-data;
        }
    }

    augment "/rt:routing/rt:control-plane-protocols/"
        + "rt:control-plane-protocol/ospf:ospf/"
        + "ospf:areas/ospf:area/ospf:interfaces/ospf:interface/"
        + "ospf:topologies/ospf:topology" {
        when "derived-from-or-self(../../../../../../../rt:type, 'ospfv2')" {
            description
              "This augmentation is only valid for OSPFv2.";
        }
        if-feature "ospf:multi-topology";
        description
          "Reverse metric configuration for the topology enabled on this
           interface.";
        uses reverse-metric-data;
    }
}
