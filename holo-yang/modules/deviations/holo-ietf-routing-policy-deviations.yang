module holo-ietf-routing-policy-deviations {
  yang-version 1.1;
  namespace "http://holo-routing.org/yang/holo-ietf-routing-policy-deviations";
  prefix holo-ietf-routing-policy-deviations;

  import ietf-routing-policy {
    prefix rt-pol;
  }

  organization
    "Holo Routing Stack";

  description
    "This module defines deviation statements for the ietf-routing-policy
     module.";

  /*
   * Default values
   */

  deviation "/rt-pol:routing-policy/rt-pol:policy-definitions/rt-pol:policy-definition/rt-pol:statements/rt-pol:statement/rt-pol:conditions/rt-pol:match-prefix-set/rt-pol:match-set-options" {
    deviate add {
      default "any";
    }
  }

  deviation "/rt-pol:routing-policy/rt-pol:policy-definitions/rt-pol:policy-definition/rt-pol:statements/rt-pol:statement/rt-pol:conditions/rt-pol:match-tag-set/rt-pol:match-set-options" {
    deviate add {
      default "any";
    }
  }

  /*
   * Added constraints
   */

  deviation "/rt-pol:routing-policy/rt-pol:policy-definitions/rt-pol:policy-definition/rt-pol:statements/rt-pol:statement/rt-pol:conditions/rt-pol:source-protocol" {
    deviate add {
      must ". = 'ietf-routing:direct'"
         + " or . = 'ietf-routing:static'"
         + " or . = 'ietf-bgp:bgp'"
         + " or . = 'ietf-isis:isis'"
         + " or . = 'ietf-ospf:ospfv2'"
         + " or . = 'ietf-ospf:ospfv3'"
         + " or . = 'ietf-rip:ripv2'"
         + " or . = 'ietf-rip:ripng'" {
        error-message
          "Invalid protocol type.";
      }
    }
  }

  /*
   * Not supported nodes
   */

  deviation "/rt-pol:routing-policy/rt-pol:policy-definitions/rt-pol:match-modified-attributes" {
    deviate not-supported;
  }
}
