module ietf-routing-policy-holo-deviations {
  yang-version 1.1;
  namespace "http://holo-routing.org/yang/ietf-routing-policy-holo-deviations";
  prefix ietf-routing-policy-holo-deviations;

  import ietf-routing-policy {
    prefix rt-pol;
  }

  organization
    "Holo Routing Stack";

  description
    "This module defines deviation statements for the ietf-routing-policy
     module.";

  /*
   * Default values
   */

  deviation "/rt-pol:routing-policy/rt-pol:policy-definitions/rt-pol:policy-definition/rt-pol:statements/rt-pol:statement/rt-pol:conditions/rt-pol:match-prefix-set/rt-pol:match-set-options" {
    deviate add {
      default "any";
    }
  }

  deviation "/rt-pol:routing-policy/rt-pol:policy-definitions/rt-pol:policy-definition/rt-pol:statements/rt-pol:statement/rt-pol:conditions/rt-pol:match-tag-set/rt-pol:match-set-options" {
    deviate add {
      default "any";
    }
  }

  /*
   * Not supported nodes
   */

  deviation "/rt-pol:routing-policy/rt-pol:policy-definitions/rt-pol:match-modified-attributes" {
    deviate not-supported;
  }
}
